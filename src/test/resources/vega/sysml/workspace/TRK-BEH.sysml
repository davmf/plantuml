package 'TRK-BEH' {
    @StrictDocWorkspace::Tracker { title = "Behaviour"; kind = "behaviour"; prefix = "BEH"; }

    public import 'BEH-001'::*;
    public import 'VIEW-001'::*;
    public import 'VIEW-002'::*;
    public import 'VIEW-003'::*;
}
