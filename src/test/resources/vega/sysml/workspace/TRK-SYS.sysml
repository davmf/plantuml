package 'TRK-SYS' {
    @StrictDocWorkspace::Tracker { title = "System requirements"; kind = "requirements"; prefix = "SYS"; }

    public import 'SYS-F-HEATING'::*;
    public import 'SYS-002'::*;
}
